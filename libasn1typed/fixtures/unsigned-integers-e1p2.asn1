UnsignedValues DEFINITIONS AUTOMATIC TAGS ::= BEGIN
Full ::= INTEGER (0..18446744073709551615)
High ::= INTEGER (9223372036854775808..18446744073709551615)
Constant ::= INTEGER (18446744073709551615..18446744073709551615)
Signed ::= INTEGER (-9223372036854775808..9223372036854775807)
Pick ::= CHOICE { inline INTEGER (0..18446744073709551615), named High }
Packet ::= SEQUENCE {
    lead BOOLEAN,
    inline INTEGER (0..18446744073709551615),
    narrow Full (9223372036854775808..18446744073709551615),
    small Full (3..7),
    optional INTEGER (9223372036854775808..18446744073709551615) OPTIONAL,
    pick Pick,
    tail BOOLEAN
}
State ::= ENUMERATED { off, on }
InlineState ::= SEQUENCE { state ENUMERATED { off, on } }
END
UnsignedExtension DEFINITIONS ::= BEGIN
BadExtension ::= INTEGER (0..18446744073709551615, ...)
END
UnsignedOverflow DEFINITIONS ::= BEGIN
BadOverflow ::= INTEGER (0..18446744073709551616)
END
UnsignedMixed DEFINITIONS ::= BEGIN
BadMixed ::= INTEGER (-1..18446744073709551615)
END
UnsignedUnion DEFINITIONS ::= BEGIN
BadUnion ::= INTEGER (0..5 | 9223372036854775808..18446744073709551615)
END
