S4ExtraBoolean DEFINITIONS AUTOMATIC TAGS ::= BEGIN
Count ::= INTEGER (0..65535)
Selection ::= CHOICE { flag BOOLEAN, amount Count }
Packet ::= SEQUENCE { count Count, enabled BOOLEAN OPTIONAL, selection Selection, extra BOOLEAN }
END
