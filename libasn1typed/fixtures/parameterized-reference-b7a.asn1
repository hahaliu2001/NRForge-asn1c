ParameterizedReferenceB7A DEFINITIONS ::= BEGIN

B7A-CLASS ::= CLASS { &id INTEGER }
SetA B7A-CLASS ::= { { &id 1 } }
SetB B7A-CLASS ::= { { &id 2 } }

Target { B7A-CLASS : Items } ::= CHOICE {
	selected BOOLEAN
}

Named ::= INTEGER
OrdinaryUse ::= CHOICE { selected Named }

UseA ::= CHOICE { selected Target {{SetA}} }
UseAAgain ::= CHOICE { selected Target {{SetA}} }
UseB ::= CHOICE { selected Target {{SetB}} }

SequenceUse ::= SEQUENCE { field Target {{SetA}} OPTIONAL }
SequenceUseB ::= SEQUENCE { field Target {{SetB}} OPTIONAL }
BadSequenceOf ::= SEQUENCE OF Target {{SetA}}

B7A-Criticality ::= ENUMERATED { reject, ignore, notify }
B7A-Presence ::= ENUMERATED { mandatory, optional, conditional }
B7A-IES ::= CLASS {
	&id INTEGER UNIQUE,
	&criticality B7A-Criticality,
	&Value,
	&presence B7A-Presence
} WITH SYNTAX { ID &id CRITICALITY &criticality TYPE &Value PRESENCE &presence }
id-root INTEGER ::= 1
B7A-Field { B7A-IES : IEs } ::= SEQUENCE {
	id B7A-IES.&id({IEs}),
	criticality B7A-IES.&criticality({IEs}{@id}),
	value B7A-IES.&Value({IEs}{@id})
}
B7A-Container { B7A-IES : IEs } ::= SEQUENCE OF B7A-Field {{IEs}}
RootIEs B7A-IES ::= {
	{ ID id-root CRITICALITY reject TYPE SequenceUse PRESENCE mandatory }
}
RootMessage ::= SEQUENCE { protocolIEs B7A-Container {{RootIEs}} }

BodySetA B7A-IES ::= {
	{ ID id-root CRITICALITY reject TYPE INTEGER PRESENCE mandatory }
}
BodySetB B7A-IES ::= {
	{ ID id-root CRITICALITY ignore TYPE BOOLEAN PRESENCE optional }
}
ShapeInner { B7A-IES : P } ::= SEQUENCE {
	id B7A-IES.&id({P}),
	criticality B7A-IES.&criticality({P}{@id}),
	value B7A-IES.&Value({P}{@id})
}
ShapeOuter { B7A-IES : P } ::= ShapeInner {{P}}
BoundBodyUse ::= SEQUENCE {
	first ShapeOuter {{BodySetA}},
	repeated ShapeOuter {{BodySetA}},
	other ShapeOuter {{BodySetB}}
}
ShapeList { B7A-IES : P } ::= SEQUENCE (SIZE (1..4)) OF ShapeInner {{P}}
SequenceOfBodyUse ::= SEQUENCE {
	itemsA ShapeList {{BodySetA}},
	itemsAAgain ShapeList {{BodySetA}},
	itemsB ShapeList {{BodySetB}}
}
id-body INTEGER ::= 101
BodyUseIEs B7A-IES ::= {
	{ ID id-body CRITICALITY reject TYPE BoundBodyUse PRESENCE mandatory }
}
BodyUseMessage ::= SEQUENCE {
	protocolIEs B7A-Container {{BodyUseIEs}}
}
id-list-body INTEGER ::= 102
SequenceOfBodyIEs B7A-IES ::= {
	{ ID id-list-body CRITICALITY reject TYPE SequenceOfBodyUse PRESENCE mandatory }
}
SequenceOfBodyMessage ::= SEQUENCE {
	protocolIEs B7A-Container {{SequenceOfBodyIEs}}
}

END
