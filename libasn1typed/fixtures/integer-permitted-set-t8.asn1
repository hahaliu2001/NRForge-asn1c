IntegerPermittedSet DEFINITIONS ::= BEGIN
RangeAndSingles ::= INTEGER (1..30 | 40 | 50, ...)
MultipleSingles ::= INTEGER (5 | 1 | 3)
MergedRanges ::= INTEGER (21 | 5..20 | 1..10)
ExpectedActivityPeriod ::= INTEGER (1..30 | 40 | 50 | 60 | 80 | 100 | 120 | 150 | 180 | 181, ...)
FieldOwner ::= SEQUENCE { value INTEGER (1..30 | 40 | 50, ...) }
END
