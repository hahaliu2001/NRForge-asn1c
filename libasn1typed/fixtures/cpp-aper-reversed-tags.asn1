CppAperReversedTags DEFINITIONS ::= BEGIN

Count ::= INTEGER (0..65535)

Selection ::= CHOICE {
    count [1] Count,
    flag  [0] BOOLEAN
}

Packet ::= SEQUENCE {
    count Count,
    enabled BOOLEAN OPTIONAL,
    selection Selection
}

END
