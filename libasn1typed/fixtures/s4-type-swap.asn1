S4TypeSwap DEFINITIONS AUTOMATIC TAGS ::= BEGIN
Count ::= INTEGER (0..65535)
Selection ::= CHOICE { flag BOOLEAN, amount Count }
Packet ::= SEQUENCE { count BOOLEAN, enabled Count OPTIONAL, selection Selection }
END
