UperFixture DEFINITIONS AUTOMATIC TAGS ::= BEGIN
Counter ::= INTEGER (0..31)
Mode ::= ENUMERATED { off(9), on(-1), ..., extra(12) }
Numbers ::= SEQUENCE (SIZE (0..3)) OF Counter
Large ::= SEQUENCE (SIZE (0..65536)) OF NULL
ExtList ::= SEQUENCE (SIZE (1..3, ...)) OF Counter
Box { T } ::= SEQUENCE { value T }
Pick ::= CHOICE { first [2] Counter, nothing [0] NULL, ..., later [7] Numbers, future [8] BOOLEAN }
Body ::= SEQUENCE {
 counter Counter DEFAULT 3,
 mode Mode DEFAULT off,
 flag BOOLEAN OPTIONAL,
 small Numbers,
 box Box { Counter },
 extList ExtList,
 ...,
 added Counter OPTIONAL,
 [[ required Counter, maybe BOOLEAN OPTIONAL, fallback Counter DEFAULT 2 ]]
}
Root ::= CHOICE { body Body, chunk Large, pick Pick, ..., later Body }
END
